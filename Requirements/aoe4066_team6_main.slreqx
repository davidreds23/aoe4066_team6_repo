# aoe4066_team6_main

## 1: Maximum Takeoff Mass (Functional)
The takeoff mass of the aircraft shall not exceed 25,000 kg.

## 2: Maximum Payload Mass (Functional)
Each payload should not exceed 10,000 kg.

## 3: Targeted Entry Year (Functional)
The fleet should be ready for service by the year 2035.

## 4: Budget (Functional)
The overall budget of the fleet shall not exceed 100 million euros.

## 5: FAA Requirements (Functional)
Must meet Title 14 Chapter 1 Subchapter C Part 25 Requirements.

## 6: Fire Detection (Functional)
Must be able to detect fires and risk areas.

## 7: Fire Suppression (Functional)
Must be able to put out fires and prevent spread to risk areas.

## 8: Takeoff Distance (Functional)
The fleet should be able to takeoff from less than 2500 feet.

## 9: Response Time (Functional)
Fleet shall be able to respond to a threat in no more than two hours.

## 10: Service Ceiling (Functional)
Service ceiling for the fleet must be at least 14,000 feet.

## 11: Temperature (Functional)
Fleet must have the ability to sustain heats of approximately 250*F.

## 12: Corrosion Resistance (Functional)
Any surfaces typically in contact with water must be resistant to corrosion.

## 13: Engine (Functional)
Aircraft shall use a TRL 9 engine.

## 14: Scooping (Functional)
Aircraft shall be able to refill water supply from existing water sources.

## 15: Range (Functional)
Aircraft should have the ability to fly a distance of 1,300 nm without refueling.

## 16: Coverage Area (Functional)
Aircraft's payload should cover () square feet of forest before refilling.

## 17: Capacity (Functional)
Aircraft should hold at least 1,000 gallons of water.

## 18: Amphibious (Functional)
Aircraft shall be able to takeoff and land on water.

## 19: STOL (Functional)
Aircraft shall be capable of short takeoff and landing.

## 20: High Lift (Functional)
Aircraft shall have high lifting wings for short takeoff and landing.

## 21: Stall Speed (Functional)
Aircraft shall have a stall speed of no more than 70 kts at MTOW.

## 22: Propulstion Type (Functional)
Aircraft should be operated using a propellor.

## 23: Water Depth (Functional)
Aircraft should operate with a minimum water depth of 5 feet.

## 24: Pilot Visibility (Functional)
The pilot should have 240 degrees of visibility.

## 25: Wave Height (Functional)
The aircraft shall sustain waves of 6 feet in height.

## 26: Land Refill Time (Functional)
When on land, tank should refill in less than 5 minutes.

## 27: Water Refill Time (Functional)
When on water, tank should refill in less than 30 seconds.

## 28: Fuel Efficiency (Functional)
The engine picked shall have high fuel efficiency.

## 29: Climb Rate (Functional)
The aircraft shall have a climb rate of 1000 ft/min.

## 30: Thrust/Weight Ratio (Functional)
Should have a high thrust/weight ratio.

## 31: Maximum Weight Factor (Functional)
Shall sustain weight factors of up to 3 g's.

## 32: Payload Drop (Functional)
Should have the ability to drop it's payload both all at once and dispersed over an area.

## 33: Engine Out (Functional)
Vertical stabilizer shall compensate for thrust moment imbalance from one engine out.

## 34: Waterproof (Functional)
Aircraft shall be water tight in places water could cause damage.

## 35: Floatation Devices (Functional)
Aircraft shall have floatation on board incase of emergency water landing.

## 36: Search and Rescue (Functional)
Fleet should be search and rescue capable.

## 37: Lights (Functional)
Aircraft shalll have exterior lights in accordance to the FAA requirements.

## 38: Air Conditioning (Functional)
Aircraft shall have A/C due to high temperature environment.

## 39: Overfill Protection (Functional)
Aircraft shall not be able to exceed its MTOW due to overfilling.

## 40: Payload Targetting (Functional)
Aircraft should use systems to accurately target and drop its payload.

## 41: Mechanical Downtime (Functional)
Aircraft should use predicitive maintenance to avoid excess mechanical downtime.

## 42: Interfleet Communication (Functional)
Aircraft shall have the ability to communicate with other vehicles within the fleet.

## 43: Color (Functional)
Aircraft shall be highly visible in both night and day conditions.

## 44: Bilge Pump (Functional)
Aircraft shall be able to remove excess water.

## 46: Impact Resistance (Functional)
Aircraft shall sustain water impacts from scooping.

## 47: Ash/Smoke Ingestion (Functional)
Engine shall still be able to work in areas of high ash/smoke concentration.

## 48: Water Ingestion (Functional)
Engine shall still be able to work despite ocean/payload spray.

## 49: Scooping Friction (Functional)
Aircraft shall sustain sudden increases in frictional forces/moments while scooping water.

## #55: Lift (Functional)
The aircraft shall produce lift equal to __

## #56: Aircraft Cost (Functional)

## FAA-21-001: Restricted Category Type Certificate – Special Purpose (Functional)
Applicant must obtain a Restricted Category Type Certificate under 14 CFR §21.25 for aerial dispensing of firefighting materials (forest and wildlife conservation). No feature or characteristic may make the aircraft unsafe when operated under limitations prescribed for its intended use.

## FAA-21-002: Special Purpose Operation – Aerial Firefighting (Functional)
The restricted category certificate must specifically list aerial dispensing of firefighting materials under §21.25(b)(2)(i) (forest and wildlife conservation).

## FAA-21-003: Compliance with Applicable Airworthiness Requirements (Functional)
Aircraft must meet the airworthiness requirements of an applicable category (Part 23 or Part 25) except those the FAA finds inappropriate for the special purpose operation.

## FAA-21-004: Noise Compliance (Functional)
Applicant must show compliance with applicable noise requirements of 14 CFR Part 36.

## FAA-21-005: Instructions for Continued Airworthiness (ICA) (Functional)
FAA-approved Instructions for Continued Airworthiness must be prepared for both the baseline aircraft and the firefighting (airtanker) mission configuration, meeting §25.1529 / §23.1529 as applicable at Amendment 54 or later.

## FAA-STR-001: Fatigue and Damage Tolerance Evaluation – Firefighting Mission (Functional)
A fatigue and damage tolerance evaluation per §25.571 (Amdt. 25-54 or later) must identify loads, internal and external, to which principal structural elements (PSEs) are subjected in the firefighting role, and determine the impact of those loads on structural integrity.

## FAA-STR-002: FAA Form 8110-3 – Fatigue Compliance Statement (Functional)
Documentation must include an FAA Form 8110-3 (Statement of Compliance with FARs) specifying in the Purpose of Data block: 'Fatigue and Damage Tolerance evaluations for the aerial dispersion mission usage' and referencing §25.571 Amdt. 25-54 or later.

## FAA-AMP-001: Hull Buoyancy Requirements (Functional)
The hull must provide buoyancy 80% in excess of that required to support the maximum weight of the airplane in fresh water.

## FAA-AMP-002: Hull Stability – No Capsize in Calm Water (Functional)
The aircraft must have sufficient margin to stay afloat at rest in calm water without capsizing in case of a likely float or hull flooding.

## FAA-AMP-003: Hull and Main Float Load Factors (Functional)
Structural load factors for the hull and main floats must be determined per §23.527 covering water landing conditions, step-turn, and planing conditions.

## FAA-AMP-004: Hull and Main Float Landing Conditions (Functional)
Design must account for hull landing conditions per §23.529, including symmetrical step landing, symmetrical bow-and-stern landing, and unsymmetrical landing.

## FAA-AMP-005: Hull Takeoff Condition (Functional)
Design must address hull takeoff loads per §23.531 accounting for spray loads and hydrodynamic lift during water takeoff acceleration.

## FAA-AMP-006: Hull Bottom Pressures (Functional)
Hull bottom pressure distribution must be determined per §23.533 for the design water load conditions.

## FAA-AMP-007: Auxiliary Float Loads (Functional)
Auxiliary float structural loads must be determined per §23.535.

## FAA-AMP-008: Seaplane Riding Lights (Functional)
Riding lights must provide a white light visible in clear atmospheric conditions for seaplane/amphibian aircraft.

## FAA-AMP-010: Seaplane Appendix I – Loads (Functional)
All applicable seaplane load criteria in Appendix I to Part 23 must be addressed in the structural analysis.

## FAA-PP-001: Engine Type Certificate – Turboprop (Functional)
Each turboprop engine must be type certificated per 14 CFR Part 33 (Airworthiness Standards: Aircraft Engines).

## FAA-PP-002: Propeller Type Certificate (Functional)
Each propeller must be type certificated per 14 CFR Part 35 (Airworthiness Standards: Propellers).

## FAA-PP-003: Engine Installation – Turboprop Compliance (Functional)
Turboprop installations must comply with Part 23 Subpart E powerplant requirements, including engine controls, fuel system, oil system, cooling, and fire protection.

## FAA-PP-004: Engine Cooling – Low-Speed / Scooping Flight Regime (Functional)
Engine cooling must be shown adequate throughout the operating envelope including low-altitude, low-speed flight during water scooping and fire drop operations.

## FAA-PP-005: Engine Fire Protection (Functional)
Each engine must be isolated in a fire zone with firewall, drain provisions, and fire detection system. Turboprop installations require flammable fluid shut-off means.

## FAA-PP-006: Propeller Clearance (Functional)
Propeller clearance from ground and water must meet minimum clearance requirements per §23.925. Must account for amphibious operations and trim at scooping attitude.

## FAA-PP-007: Engine Ice Protection (Functional)
Engine induction system ice protection must be provided and demonstrated effective throughout the required flight envelope.

## FAA-PP-008: One Engine Inoperative (OEI) Performance (Functional)
Aircraft must demonstrate climb performance with one engine inoperative at the appropriate certification level, including at the maximum scooping/dispensing weight.

## FAA-FF-001: Retardant/Water Tank System Design (Functional)
The onboard water/retardant tank and dispensing system must be designed and installed as a certified modification (STC or TC change). System must not adversely affect flight characteristics, structural integrity, or any aircraft system.

## FAA-FF-002: Drop Door / Dispensing System – Structural Loads (Functional)
Structural loads imparted by the water/retardant dispensing system (fill, carry, drop) must be evaluated and shown not to exceed design limit loads for the airframe.

## FAA-FF-003: Scooping System Intake – Hydrodynamic and Structural (Functional)
The water intake scoop system must be structurally evaluated for hydrodynamic drag loads during scooping at approved scoop speeds and sea states.

## FAA-FF-004: Retardant Chemical Compatibility (Functional)
All materials in the tank, dispensing system, and potentially exposed airframe areas must be shown compatible with fire retardant chemicals used in the mission (ammonium polyphosphate-based retardants and water).

## FAA-FF-005: Flight Manual Supplement – Firefighting Operations (Functional)
An FAA-approved Airplane Flight Manual Supplement (AFMS) must be prepared covering the firefighting mission, including scooping speeds, drop speeds, system operating procedures, emergency procedures, and performance data.

## FAA-FF-006: Placards and Markings – Mission Equipment (Functional)
All mission-specific controls (tank, scoop, drop doors) must be labeled with appropriate placards per §23.1555 and §23.1557.

## FAA-OPS-001: Airworthiness Certificate – Restricted Category (Functional)
Aircraft must hold a current and valid restricted category airworthiness certificate issued per §21.183 / §21.185 and displayed per §91.203.

## FAA-OPS-002: Operational Limitations – Restricted Category (Functional)
The aircraft must be operated in accordance with the limitations of its restricted category certificate. Operations over populated areas and in congested airways require FAA waiver per §91.313.

## FAA-OPS-003: Annual / Periodic Inspection (Functional)
Turbopropeller-powered multiengine airplanes must operate under an FAA-approved inspection program per §91.409(e), rather than a standard annual inspection.

## FAA-OPS-004: Fuel Venting and Exhaust Emissions (Functional)
Aircraft must comply with fuel venting and exhaust emission requirements of 14 CFR Part 34.

## P25-A-001: Applicability – Transport Category (Functional)
Part 25 prescribes airworthiness standards for the issuance of type certificates and changes to those certificates for transport category airplanes. Applies to propeller-driven airplanes with MTOW > 19,000 lb or > 19 seats.

## P25-B-001: Proof of Compliance – Flight (Functional)
Each requirement of Subpart B must be met at each appropriate combination of airspeed and engine power covering the complete operational envelope, including the firefighting and water scooping configuration.

## P25-B-002: Weight and CG Limits (Functional)
Maximum and minimum weights and center of gravity limits must be established for all configurations, including the water/retardant loaded condition (full tank), partially filled, and empty tank states.

## P25-B-003: Propeller Speed and Pitch Limits (Functional)
Propeller speed and pitch limits must be established for the turboprop installation that are not exceeded in any normal operation including the maximum power scooping and drop maneuvers.

## P25-B-004: Stall Speed (Functional)
The stall speed VS1 (flaps up) and VS0 (landing configuration) must be determined. These form the basis for all other speed scheduling requirements.

## P25-B-005: Takeoff Performance (Functional)
Takeoff distance, takeoff run, and takeoff flight path must be determined at maximum takeoff weight, including water-laden (post-scoop) configuration, at the critical combinations of altitude and temperature.

## P25-B-006: Takeoff Speeds – V1, VR, V2 (Functional)
Decision speed V1, rotation speed VR, and takeoff safety speed V2 must be established for all takeoff configurations including the water-laden state post-scooping.

## P25-B-007: Accelerate-Stop Distance (Functional)
Accelerate-stop distance must be determined for both land and water operations. The water accelerate-stop distance is particularly critical given limited water runway lengths at fire bases.

## P25-B-008: Climb: All-Engines-Operating (Functional)
Climb gradient requirements must be met with all engines operating in the takeoff and en route configurations at the relevant weights including maximum water/retardant load.

## P25-B-009: Climb: One-Engine-Inoperative (OEI) (Functional)
The aircraft must meet OEI climb gradient requirements (§25.121) in all segments of flight. Net climb gradient with OEI in the final takeoff configuration must be ≥ 1.2% (twin turboprop, 2 engines). Critical scenario includes OEI during low-altitude scooping run.

## P25-B-010: En Route Flight Paths – OEI (Functional)
En route net flight path with one engine inoperative must clear all obstacles by 1,000 ft (IFR) or 2,000 ft (IFR mountainous) along the planned operational routes.

## P25-B-011: Landing Performance (Functional)
Landing distance must be established for both land and water operations at the maximum landing weight. For water landings, the limiting conditions applicable to amphibious operations must be included.

## P25-B-012: Controllability and Maneuverability – General (Functional)
The airplane must be safely controllable and maneuverable during all stages of flight including takeoff, climb, cruise, descent, approach, and landing, in each configuration including water scoop deployed.

## P25-B-013: Longitudinal Control (Functional)
It must be possible to pitch the nose down to recover from stall using primary controls at any speed, altitude, and configuration including full water/retardant load.

## P25-B-014: Minimum Control Speeds – Vmca and Vmcg (Functional)
Minimum control speed in the air (Vmca) and on the ground (Vmcg) must be determined for the turboprop configuration. Vmcl (landing) must also be demonstrated.

## P25-B-015: Trim (Functional)
The airplane must maintain level flight hands-off with the most critical combination of weight, altitude, speed, and power settings including post-drop (sudden CG shift) condition.

## P25-B-016: Static Longitudinal, Lateral-Directional Stability (Functional)
The aircraft must demonstrate positive static longitudinal stability (§25.173) and acceptable lateral-directional stability (§25.177) throughout the operational envelope including all loading states.

## P25-B-017: Dynamic Stability (Functional)
Any short-period oscillation and phugoid mode must meet the dynamic stability criteria of §25.181 throughout the flight envelope.

## P25-B-018: Stall Characteristics and Warning (Functional)
The aircraft must demonstrate acceptable stall characteristics with adequate pre-stall warning (§25.207) in all configurations including scoop deployed and water tank full/empty.

## P25-B-W01: Longitudinal Stability and Control on Water (Functional)
The aircraft must demonstrate satisfactory longitudinal stability and control while on water, including during the water scooping acceleration/deceleration run.

## P25-B-W02: Directional Stability and Control on Water (Functional)
The aircraft must have satisfactory directional control during straight taxiing and step turns on water at all loading states and in all crosswind conditions up to the maximum demonstrated crosswind.

## P25-B-W03: Taxiing Condition on Water (Functional)
The aircraft must be controllable on water under expected sea state conditions. Taxiing ability in rough water must be evaluated.

## P25-B-W04: Wind Velocities for Water Operations (Functional)
Maximum demonstrated crosswind and headwind/tailwind components for water takeoff and landing must be established and documented in the AFM.

## P25-B-W05: Spray Characteristics, Control, and Stability on Water (Functional)
The spray generated during water operations (particularly high-speed scooping runs) must not impair pilot visibility or adversely affect propeller, engine inlet, control surfaces, or any other critical system.

## P25-B-W06: Vibration and Buffeting (Functional)
There must be no buffeting in any normal flight condition severe enough to interfere with control of the aircraft or to cause excessive fatigue. This must be evaluated with scoop deployed.

## P25-C-001: Loads – General (Functional)
Structural loads must be determined for all critical combinations of weight, altitude, speed, and configuration. Must include mission-specific loads: water-laden takeoff, drop maneuver transients, and scoop deployment/retraction loads.

## P25-C-002: Factor of Safety (Functional)
A factor of safety of 1.5 must be applied to all limit loads to determine ultimate loads. All structure must withstand ultimate loads without failure.

## P25-C-003: Strength and Deformation (Functional)
The structure must be able to support limit loads without detrimental permanent deformation, and ultimate loads for at least 3 seconds without failure.

## P25-C-004: Flight Maneuvering Envelope – V-n Diagram (Functional)
The flight maneuvering envelope (V-n diagram) must be established encompassing all approved configurations including the water/retardant loaded and empty states.

## P25-C-005: Gust and Turbulence Loads (Functional)
The aircraft structure must withstand gust loads per §25.341 for discrete gusts and continuous turbulence. Low-altitude turbulence encountered during fire drops must be considered.

## P25-C-006: Engine Torque Loads – Turboprop (Functional)
Structural loads due to turboprop engine torque, including gyroscopic loads from propeller, must be accounted for in the engine mount and nacelle structure design.

## P25-C-007: Unsymmetrical Loads due to Engine Failure (Functional)
The structure must withstand loads resulting from sudden failure of one turboprop engine, including torque reaction and propeller drag loads.

## P25-C-008: Landing Gear – Land Landing Load Conditions (Functional)
Landing gear and supporting structure must withstand the critical land landing conditions at maximum landing weight per §25.473–§25.511.

## P25-C-W01: Seaplane Load Conditions – General (Functional)
Structural loads for all water operations must be determined per §25.521–§25.537, covering the symmetric and unsymmetrical step landing, stern landing, bow landing, and planing conditions.

## P25-C-W02: Hull and Main Float Load Factors (Functional)
Water load factors for the hull must be determined per §25.527 for step, stern, and bow loading conditions at the design weights and CG positions.

## P25-C-W03: Hull and Main Float Landing Conditions (Functional)
The hull must be designed for the step, bow, stern, and unsymmetrical landing conditions per §25.529. Each condition represents a critical load case for hull and fuselage structure.

## P25-C-W04: Hull and Main Float Takeoff Condition (Functional)
The hull structure must withstand the hydrodynamic and aerodynamic loads occurring during the water takeoff run, including the unstick condition and spray loads.

## P25-C-W05: Hull and Main Float Bottom Pressures (Functional)
Local hull bottom pressure distribution must be determined per §25.533 and applied to the hull plating and frame design.

## P25-C-W06: Auxiliary Float Loads (Functional)
Auxiliary float structural loads (wingtip floats) must be determined per §25.535 covering the water contact and spray conditions.

## P25-C-W07: Seawing Loads (Functional)
If seawings (sponsons or stub wings) are used to provide buoyancy or spray suppression, their loads must be determined per §25.537.

## P25-C-E01: Emergency Landing – General (Functional)
The aircraft structure must provide occupant protection under emergency landing conditions per §25.561 (g = 9.0 forward, 1.5 sideward, 6.0 downward for crew, etc.).

## P25-C-E02: Emergency Landing Dynamic Conditions (Functional)
Seat and occupant restraint systems must meet the dynamic load requirements of §25.562 to protect occupants under emergency crash conditions.

## P25-C-F01: Damage Tolerance and Fatigue Evaluation – Firefighting Mission (Functional)
A damage tolerance evaluation per §25.571 (Amendment 25-54 or later) must be performed for all principal structural elements (PSEs). The evaluation must specifically address loads from the firefighting mission: scooping hydrodynamic loads, drop transients, and repeated water landings.

## P25-C-F02: PSE Identification and Load Spectrum (Functional)
All principal structural elements must be identified and mission load spectra must be developed encompassing the full firefighting mission profile including ferry, transit, scooping, fire drop, and water operations cycles.

## P25-C-F03: Lightning Protection – Structure (Functional)
The aircraft structure must provide lightning protection per §25.581 to prevent ignition of fuel vapors or damage to flight-critical structure from direct or swept lightning strikes.

## P25-D-001: Materials (Functional)
All materials used in the type design must meet approved specifications. Corrosion resistance of hull, tank, and exposed structure must be demonstrated against water and retardant chemical exposure.

## P25-D-002: Fabrication Methods (Functional)
All fabrication methods must be approved. Special attention required for hull joints, scoop attachment structure, and water/retardant tank construction.

## P25-D-003: Aeroelastic Stability (Functional)
The aircraft must be free from flutter, divergence, and control reversal at all speeds up to VD/MD throughout the operational envelope, including with scoop deployed and tank in all filling states.

## P25-D-004: Bird Strike Damage (Functional)
The windshield and forward-facing structure must be designed to withstand a bird strike of 4 lbs at the aircraft's maximum approach speed.

## P25-D-005: Flight Control Systems – General (Functional)
All flight control systems must meet the requirements of §25.671–§25.703. Any mission system actuation (scoop, drop door) must not interfere with primary flight controls.

## P25-D-006: Landing Gear Retracting Mechanism (Functional)
The landing gear retraction mechanism must function reliably and the gear must be capable of extension by alternate means. Water ingestion into gear bays during water operations must be evaluated.

## P25-D-H01: Main Float Buoyancy (Functional)
If fitted with main floats, each must provide sufficient buoyancy per §25.751 with the required 80% excess buoyancy margin.

## P25-D-H02: Main Float Design (Functional)
Main floats must be designed per §25.753 to withstand the water loads defined in Subpart C and must provide the required buoyancy margin.

## P25-D-H03: Hull Design (Functional)
The hull must be watertight, provide adequate buoyancy, and meet all the structural load requirements of §25.521–§25.537. The water scoop intake must be integrated without compromising hull watertightness.

## P25-D-F01: Flammable Fluid Fire Protection (Functional)
All flammable fluid lines, fittings, and components must be shielded or located to minimize fire risk. Drainage provisions must prevent accumulation of flammable fluids in any area. Retardant foam concentrate (if used) must be assessed for fire risk.

## P25-D-F02: Fire Protection of Flight Controls and Engine Mounts (Functional)
Flight control systems, engine mounts, and other flight structure in designated fire zones must be fire resistant or fireproof.

## P25-E-001: Powerplant Installation – General (Functional)
Each powerplant installation must meet the requirements of §25.901. All engine and propeller systems must be designed and installed so that no single failure or malfunction of any part will prevent continued safe flight and landing.

## P25-E-002: Engine Installation – Turbine (Functional)
Each turboprop engine installation must comply with §25.903 including engine restart capability in flight, precautions against engine failure, and isolation provisions.

## P25-E-T01: Propellers – Turboprop (Functional)
Each propeller installation must comply with §25.905, including certification per Part 35, and must meet all installation, clearance, and safety requirements.

## P25-E-T02: Propeller Vibration and Fatigue (Functional)
Each propeller must be shown to be free from harmful vibration and to have adequate fatigue strength under all conditions throughout the approved operating range, including mission-specific load cycles.

## P25-E-T03: Propeller Clearance – Water Operations (Functional)
Propeller tip clearance from the water surface during taxiing, takeoff run, and landing must be sufficient to prevent blade strike. Must be evaluated at the critical (most nose-down) attitude on water.

## P25-E-T04: Propeller De-Icing (Functional)
Propeller de-icing system must be provided and shown effective for flight in icing conditions per §25.929.

## P25-E-T05: Turbopropeller-Drag Limiting Systems (Functional)
A turboprop drag-limiting system (propeller auto-feather or torque limiter) must be installed to limit propeller drag to within structural limits upon engine failure.

## P25-E-T06: Turbine Engine Operating Characteristics (Functional)
All operating characteristics of the turboprop engines must be evaluated to ensure there are no adverse characteristics, including stall, surge, flameout, or compressor instability, throughout the flight envelope including rapid throttle movements during scooping.

## P25-E-T07: Propeller Reversing Systems (Functional)
If propeller reversing is installed for water braking (post-scoop deceleration), the reversing system must comply with §25.933, including prevention of unintended reversal and structural adequacy.

## P25-E-T08: Inlet, Engine, and Exhaust Compatibility (Functional)
Engine inlets must be free from unacceptable distortion throughout the operating envelope including water spray conditions during scooping. Exhaust systems must not create hazards.

## P25-E-F01: Fuel System – General (Functional)
The fuel system must meet §25.951–§25.973 requirements including independence, flow, hot-weather operation, and tank design. Tank installation must be evaluated for corrosion resistance to water/retardant exposure.

## P25-E-F02: Fuel System Lightning Protection (Functional)
The fuel system must be protected against lightning-induced ignition sources per §25.954.

## P25-E-O01: Engine Cooling (Functional)
Engine cooling must be shown adequate under the most critical combination of conditions including maximum continuous power at minimum airspeed (scooping configuration). Cowl flap position and control must be evaluated.

## P25-E-O02: Induction System Ice Protection (Functional)
Engine air induction system ice protection must be provided and demonstrated effective in the icing conditions defined in Appendix C to Part 25 (and Appendix O if SLD conditions are sought).

## P25-E-FP01: Engine Fire Protection – Zones and Firewalls (Functional)
Each engine must be enclosed in a designated fire zone with approved firewall, drainage, and fire-resistant materials per §25.1181–§25.1193.

## P25-E-FP02: Engine Fire Extinguishing System (Functional)
Each engine fire zone must have a fire extinguishing system capable of extinguishing any fire that could occur, with at least two shots available per §25.1195–§25.1201.

## P25-E-FP03: Engine Fire Detection System (Functional)
An approved fire detection system must be installed in each engine fire zone per §25.1203. The system must provide timely warning with minimum false alarms.

## P25-F-001: Function and Installation – Equipment General (Functional)
All equipment and installations must function as intended under all operating conditions. Mission equipment (tank, scoop, drop doors) must not adversely affect any airworthiness-related aircraft system.

## P25-F-002: Equipment Systems and Installations – Safety Analysis (Functional)
Equipment, systems, and installations must be designed so that any single failure or probable combination of failures does not prevent continued safe flight and landing. This applies to the mission system (tank, scoop, doors) and any aircraft systems it interfaces with.

## P25-F-003: Flight and Navigation Instruments (Functional)
Required flight instruments must be installed per §25.1303, including all instruments needed for the approved operations (IFR if applicable) and any mission-specific instrumentation.

## P25-F-004: HIRF and Lightning Protection – Equipment (Functional)
Electrical and electronic systems must be protected against High Intensity Radiated Fields (HIRF) per §25.1317 and lightning indirect effects per §25.1316.

## P25-G-001: Airspeed Limitations (Functional)
Maximum operating speed VMO, design maneuvering speed VA, flap extension speed VFE, landing gear speeds VLE/VLO, and all other speed limitations must be established.

## P25-G-002: Minimum Flight Crew (Functional)
The minimum flight crew must be established based on workload analysis per §25.1523. Mission workload during scooping and fire drop must be included in the analysis.

## P25-G-003: Instructions for Continued Airworthiness (ICA) (Functional)
FAA-approved ICAs must be prepared per §25.1529 and Appendix H to Part 25 for the baseline aircraft and specifically for the firefighting mission configuration, incorporating inspection intervals from the fatigue/damage tolerance evaluation.

## P25-G-004: Powerplant Limitations (Functional)
All turboprop engine operating limitations must be established and approved per §25.1521, including all power ratings (takeoff, max continuous, cruise) and operational limits.

## P25-G-005: Airplane Flight Manual (Functional)
An FAA-approved AFM must be prepared per §25.1581–§25.1587 containing all required limitations, normal/abnormal/emergency procedures, and performance data. An AFMS covering the firefighting mission must be included.

## P25-H-001: EWIS – General Requirements (Functional)
All electrical wiring interconnection systems (EWIS) must be designed, installed, and maintained per §25.1701–§25.1733. Mission system wiring must be segregated from flight-critical EWIS.

## P25-H-002: EWIS – Fire Protection (Functional)
All EWIS in designated fire zones must be fireproof or fire-resistant per §25.1713. Wiring routes must minimize fire risk.

## P25-H-003: EWIS – Bonding and Static Electricity (Functional)
All EWIS must incorporate adequate electrical bonding and protection against static electricity per §25.1715.

## P25-H-004: EWIS – ICA (Functional)
Instructions for Continued Airworthiness for the EWIS must be prepared per §25.1729.

## P25-FF-001: Water/Retardant Tank System – Design and Integration (Functional)
The water/retardant tank must be designed, qualified, and installed as a certified modification. It must not adversely affect the structural integrity, flight characteristics, or any aircraft system. Tank fill, carry, and dump loads must be fully defined.

## P25-FF-002: Water Scoop System – Structural and Hydrodynamic Qualification (Functional)
The water scoop must be structurally qualified for the combined aerodynamic and hydrodynamic loads during deployment at the maximum scoop speed. A special conditions issue paper is anticipated for this novel design feature.

## P25-FF-003: Drop Door / Dispensing System – Loads and Structural Integrity (Functional)
Drop door actuators, hinges, and the surrounding airframe structure must withstand the aerodynamic and inertial loads during door operation at all approved drop speeds and altitudes.

## P25-FF-004: Retardant Chemical Compatibility – Airframe and Systems (Functional)
All materials exposed to fire retardant chemicals (ammonium polyphosphate, water, foam additives) must be evaluated for compatibility. This includes hull plating, seals, hoses, electrical connectors, and any co-located aircraft systems.

## P25-FF-005: Flight Manual Supplement – Firefighting Operations (Functional)
An FAA-approved AFMS must cover: approved scooping speeds, maximum drop speed, tank fill procedures, drop procedures, abort criteria, emergency jettison, water taxi procedures, and all mission-specific performance data.

## P25-FF-006: Mission-Specific Placards and Markings (Functional)
All mission-specific controls and equipment (water tank gauges, scoop control, drop door control, jettison) must have clear and approved placards per §25.1541–§25.1557.

## P25-FF-007: Emergency Jettison System (Functional)
A means to jettison the water/retardant load in an emergency must be provided if carried. The jettison system must be operable by the flight crew without requiring unusual skill or strength, and operation must not endanger the aircraft or endanger persons on the ground.

## #220: Justifications
